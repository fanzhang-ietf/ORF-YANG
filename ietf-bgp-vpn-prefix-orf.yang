module ietf-bgp-vpn-prefix-orf {
  yang-version 1.1;
  namespace
    "urn:ietf:params:xml:ns:yang:ietf-bgp-vpn-prefix-orf";
  prefix vporf;

  import ietf-routing-types {
    prefix rt-types;
    reference
      "RFC 8294: Common YANG Data Types for the Routing Area";
  }
  import ietf-routing {
    prefix rt;
    reference
      "RFC 8349: A YANG Data Model for Routing Management
                 (NMDA Version)";
  }
  import ietf-inet-types {
    prefix inet;
    reference
      "RFC 9911: Common YANG Data Types";
  }
  import ietf-bgp {
    prefix bgp;
    reference
      "RFC XXXX: YANG Model for Border Gateway Protocol (BGP-4)";
  }
  import ietf-bgp-orf {
    prefix orf;
    reference
      "RFC XXXX: YANG Data Model for BGP Outbound Route Filtering";
  }  

  organization
    "IETF Inter-Domain Routing (IDR) Working Group";

  contact
    "WG Web:   https://datatracker.ietf.org/wg/idr
     WG List:  IDR <mailto:idr@ietf.org>

     Editor:   Fan Zhang
               <mailto:zhangf52@chinatelecom.cn>
     Editor:   Aijun Wang
               <mailto:wangaj3@chinatelecom.cn>
     Editor:   Changwang Lin
               <mailto:linchangwang.04414@h3c.com>";
  description
    "This YANG module defines a generic configuration and operational
     state for VPN Prefix ORF, including VPN Prefix ORF quota and
     overload handling.

     The key words 'MUST', 'MUST NOT', 'REQUIRED', 'SHALL', 'SHALL
     NOT', 'SHOULD', 'SHOULD NOT', 'RECOMMENDED', 'NOT RECOMMENDED',
     'MAY', and 'OPTIONAL' in this document are to be interpreted as
     described in BCP 14 (RFC 2119) (RFC 8174) when, and only when,
     they appear in all capitals, as shown here.

     Copyright (c) 2026 IETF Trust and the persons identified as
     authors of the code. All rights reserved.

     Redistribution and use in source and binary forms, with or
     without modification, is permitted pursuant to, and subject to
     the license terms contained in, the Revised BSD License set
     forth in Section 4.c of the IETF Trust's Legal Provisions
     Relating to IETF Documents
     (https://trustee.ietf.org/license-info).

     All revisions of IETF and IANA published modules can be found
     at the YANG Parameters registry group
     (https://www.iana.org/assignments/yang-parameters).

     This version of this YANG module is part of RFC XXXX; see
     the RFC itself for full legal notices.";

  revision 2026-06-18 {
    description
      "Initial revision.";
    reference
      "RFC XXXX: VPN Prefix Outbound Route Filter (VPN Prefix ORF)
                 for BGP-4";
  }

  /*
   * Features
   */

  feature vpn-prefix-orf {
    description
      "Support for VPN Prefix ORF for BGP-4.";
    reference
      "RFC XXXX: VPN Prefix Outbound Route Filter (VPN Prefix ORF)
                 for BGP-4";    
  }
  
  /*
   * Identities
   */  

  identity vpn-prefix-orf {
    base orf:orf-type;
    description
      "VPN Prefix ORF.";
    reference
      "RFC XXXX: VPN Prefix Outbound Route Filter (VPN Prefix ORF)
                 for BGP-4";    
  }

  /*
   * Typedefs
   */

  typedef source-pe-identifier {
    type uint32;
    description
      "Source PE identifier carried by VPN Prefix ORF.";
  }

  typedef overload-process-method-type {
    type enumeration {
      enum withdraw-overload-routes {
        value 0;
        description
          "The receiver of VPN Prefix ORF message MUST withdraw all
           previously advertised overload VPN routes that match the
           ORF's type-specific part.";
      }
      enum refuse-overload-routes {
        value 1;
        description
          "The sender of the VPN Prefix ORF message will refuse to
           accept VPN routes matching the overload criteria and that
           the receiver of the VPN Prefix ORF message MUST NOT
           announce VPN routes matching the overload criteria.";
      }
      
    }
    description
      "Overload VPN routes process method";
    reference
      "RFC XXXX: VPN Prefix Outbound Route Filter (VPN Prefix ORF)
                 for BGP-4,Section 4";      
  }

  /*
   * Groupings
   */

  grouping vpn-prefix-orf-quotas {
    description
      "Grouping of VPN Prefix ORF quotas.";
    container vpn-prefix-orf-quotas {
      description
        "Quota configuration for granular mode.
         If no quota entries are configured, VPN Prefix ORF operates
         in basic mode.";
      list vpn-prefix-orf-quota {
        key "rd source-pe";
        description
          "List of quotas per <RD, Source PE>.";
        leaf rd {
          type rt-types:route-distinguisher;
          description 
            "Route distinguisher for which the quota applies.";
        }
        leaf source-pe {
          type union {
            type inet:ip-address;
            type uint32;
          }
          description
            "Source PE for which the quota applies.";          
        }
        leaf quota-value {
          type uint32;
          description
            "Threshold to limit the number of VPN routes";
        }
        leaf overload-process-method {
          type overload-process-method-type;
          default "withdraw-overload-routes";
          description
            "Overload VPN routes process method";
        }
        reference
          "RFC XXXX: VPN Prefix Outbound Route Filter
                     (VPN Prefix ORF) for BGP-4, Section 7.2";
      }
    }
  }

  grouping vpn-prefix-orf-entries {
    description
      "Grouping of VPN Prefix ORF entries";
    list vpn-prefix-orf-entry {
      key "sequence";
      description
        "List of VPN Prefix ORF entries of an address family.";
      leaf sequence {        
        type uint32;
        description
          "The relative ordering of the entry among all the VPN
           Prefix ORF entries.";
      }
      leaf match {
        type enumeration {
          enum permit {
            description
              "Permit the peer to pass updates for the set of routes
               that match the ORF entry.";
          }
          enum deny {
            description
              "Deny the peer to pass updates for the set of routes
               that match the ORF entry.";
          }
        }
        description
          "Specifiying whether this entry is PERMIT or DENY. VPN
           Prefix ORF entry is only valid when its Match field is
           DENY.";
      }
      leaf rd {
        type rt-types:route-distinguisher;
        description "Route distinguisher";
      }
      leaf overload-process-method {
        type overload-process-method-type;
        description
          "Overload VPN routes process method";
        reference
          "RFC XXXX: VPN Prefix Outbound Route Filter
                     (VPN Prefix ORF) for BGP-4, Section 4";
      }
      choice source-pe {
        description
          "Source PE information associated with the ORF entry.";

        case ipv4 {
          leaf ipv4-address {
            type inet:ipv4-address;
            description
              "IPv4 Source PE TLV.";
          }
        }

        case ipv6 {
          leaf ipv6-address {
            type inet:ipv6-address;
            description
              "IPv6 Source PE TLV.";
          }
        }

        case identifier {
          leaf source-pe-identifier {
            type source-pe-identifier;
            description
              "Source PE identifier TLV.";
          }
        }
        reference
          "RFC XXXX: VPN Prefix Outbound Route Filter
                     (VPN Prefix ORF) for BGP-4, Section 4.1";
      }      
      leaf-list route-target {
        type rt-types:route-target;
        
        description
          "Optional Route Target match criteria of the VPN Prefix
           ORF entry. When present, only VPN routes carrying one
           of the specified Route Target values are matched.";
        reference
          "RFC XXXX: VPN Prefix Outbound Route Filter
                     (VPN Prefix ORF) for BGP-4, Section 4.2";
      }
      leaf route-type {
        type uint8;
        description
          "The route type value carried in the Route Type TLV.";
        reference
          "RFC XXXX: VPN Prefix Outbound Route Filter
                     (VPN Prefix ORF) for BGP-4, Section 4.3";
      }  
    }
  }

  /*
   * Data nodes
   */  

  augment 
   "/rt:routing/rt:control-plane-protocols"
  +"/rt:control-plane-protocol/bgp:bgp/bgp:neighbors/bgp:neighbor"
  +"/bgp:afi-safis/bgp:afi-safi/bgp:l3vpn-ipv4-unicast" {
    if-feature "vpn-prefix-orf";
    description
      "VPN Prefix ORF augmentation for the L3VPN IPv4 unicast
       address family of a BGP neighbor.";
    uses orf:orf-capability;
    uses vpn-prefix-orf-quotas;
    container vpn-prefix-orf-entries-sent {
      config false;
      description
        "VPN Prefix ORF entries sent";
      uses vpn-prefix-orf-entries;
    }
    container vpn-prefix-orf-entries-received {
      config false;
      
      description
        "VPN Prefix ORF entries received";
      uses vpn-prefix-orf-entries;
    }
  }  
  
  augment
   "/rt:routing/rt:control-plane-protocols"
  +"/rt:control-plane-protocol/bgp:bgp/bgp:neighbors/bgp:neighbor"
  +"/bgp:afi-safis/bgp:afi-safi/bgp:l3vpn-ipv6-unicast" {
    if-feature "vpn-prefix-orf";        
    description
      "VPN Prefix ORF augmentation for the L3VPN IPv6 unicast
       address family of a BGP neighbor.";
    uses orf:orf-capability;
    uses vpn-prefix-orf-quotas;
    container vpn-prefix-orf-entries-send {
      config false;
      description
        "VPN Prefix ORF entries sent";
      uses vpn-prefix-orf-entries;
    }
    container vpn-prefix-orf-entries-received {
      config false;
      
      description
        "VPN Prefix ORF entries received";
      uses vpn-prefix-orf-entries;
    }
  }

  augment 
   "/rt:routing/rt:control-plane-protocols"
  +"/rt:control-plane-protocol/bgp:bgp/bgp:neighbors/bgp:neighbor"
  +"/bgp:afi-safis/bgp:afi-safi/bgp:l3vpn-ipv4-multicast" {
    if-feature "vpn-prefix-orf";
    description
      "VPN Prefix ORF augmentation for the L3VPN IPv4 multicast
       address family of a BGP neighbor.";
    uses orf:orf-capability;
    uses vpn-prefix-orf-quotas;
    container vpn-prefix-orf-entries-sent {
      config false;
      description
        "VPN Prefix ORF entries sent";
      uses vpn-prefix-orf-entries;
    }
    container vpn-prefix-orf-entries-received {
      config false;
      
      description
        "VPN Prefix ORF entries received";
      uses vpn-prefix-orf-entries;
    }
  }  
  
  augment
   "/rt:routing/rt:control-plane-protocols"
  +"/rt:control-plane-protocol/bgp:bgp/bgp:neighbors/bgp:neighbor"
  +"/bgp:afi-safis/bgp:afi-safi/bgp:l3vpn-ipv6-multicast" {
    if-feature "vpn-prefix-orf";        
    description
      "VPN Prefix ORF augmentation for the L3VPN IPv6 multicast
       address family of a BGP neighbor.";
    uses orf:orf-capability;
    uses vpn-prefix-orf-quotas;
    container vpn-prefix-orf-entries-send {
      config false;
      description
        "VPN Prefix ORF entries sent";
      uses vpn-prefix-orf-entries;
    }
    container vpn-prefix-orf-entries-received {
      config false;
      
      description
        "VPN Prefix ORF entries received";
      uses vpn-prefix-orf-entries;
    }
  }

  augment
   "/rt:routing/rt:control-plane-protocols"
  +"/rt:control-plane-protocol/bgp:bgp/bgp:neighbors/bgp:neighbor"
  +"/bgp:afi-safis/bgp:afi-safi/bgp:l2vpn-vpls" {
    if-feature "vpn-prefix-orf";
    description
      "VPN Prefix ORF augmentation for the L2VPN VPLS address family
       of a BGP neighbor.";
    uses orf:orf-capability;
    uses vpn-prefix-orf-quotas;
    container vpn-prefix-orf-entries-sent {
      config false;
      description
        "VPN Prefix ORF entries sent";
      uses vpn-prefix-orf-entries;
    }
    container vpn-prefix-orf-entries-received {
      config false;
      
      description
        "VPN Prefix ORF entries received";
      uses vpn-prefix-orf-entries;
    }
  }  
  
  augment
   "/rt:routing/rt:control-plane-protocols"
  +"/rt:control-plane-protocol/bgp:bgp/bgp:neighbors/bgp:neighbor"
  +"/bgp:afi-safis/bgp:afi-safi/bgp:l2vpn-evpn" {
    if-feature "vpn-prefix-orf";        
    description
      "VPN Prefix ORF augmentation for the L2VPN EVPN address family
       of a BGP neighbor.";
    uses orf:orf-capability;
    uses vpn-prefix-orf-quotas;
    container vpn-prefix-orf-entries-send {
      config false;
      description
        "VPN Prefix ORF entries sent";
      uses vpn-prefix-orf-entries;
    }
    container vpn-prefix-orf-entries-received {
      config false;
      
      description
        "VPN Prefix ORF entries received";
      uses vpn-prefix-orf-entries;
    }
  }   
  
  augment
   "/rt:routing/rt:control-plane-protocols"
  +"/rt:control-plane-protocol/bgp:bgp/bgp:peer-groups"
  +"/bgp:peer-group/bgp:afi-safis/bgp:afi-safi"
  +"/bgp:l3vpn-ipv4-unicast" {
    if-feature "vpn-prefix-orf";
    description
      "VPN Prefix ORF augmentation for the L3VPN IPv4 unicast
       address family of a BGP peer group.";
    uses orf:orf-capability;
    uses vpn-prefix-orf-quotas;
  }  
  
  augment
   "/rt:routing/rt:control-plane-protocols"
  +"/rt:control-plane-protocol/bgp:bgp/bgp:peer-groups"
  +"/bgp:peer-group/bgp:afi-safis/bgp:afi-safi"
  +"/bgp:l3vpn-ipv6-unicast" {
    if-feature "vpn-prefix-orf";        
    description
      "VPN Prefix ORF augmentation for the L3VPN IPv6 unicast
       address family of a BGP peer group.";
    uses orf:orf-capability;
    uses vpn-prefix-orf-quotas;
  }
  augment
   "/rt:routing/rt:control-plane-protocols"
  +"/rt:control-plane-protocol/bgp:bgp/bgp:peer-groups"
  +"/bgp:peer-group/bgp:afi-safis/bgp:afi-safi"
  +"/bgp:l3vpn-ipv4-multicast" {
    if-feature "vpn-prefix-orf";
    description
      "VPN Prefix ORF augmentation for the L3VPN IPv4 multicast
       address family of a BGP peer group.";
    uses orf:orf-capability;
    uses vpn-prefix-orf-quotas;
  }  
  augment
   "/rt:routing/rt:control-plane-protocols"
  +"/rt:control-plane-protocol/bgp:bgp/bgp:peer-groups"
  +"/bgp:peer-group/bgp:afi-safis/bgp:afi-safi"
  +"/bgp:l3vpn-ipv6-multicast" {
    if-feature "vpn-prefix-orf";        
    description
      "VPN Prefix ORF augmentation for the L3VPN IPv6 multicast
       address family of a BGP peer group.";
    uses orf:orf-capability;
    uses vpn-prefix-orf-quotas;
  }  
  augment
   "/rt:routing/rt:control-plane-protocols"
  +"/rt:control-plane-protocol/bgp:bgp/bgp:peer-groups"
  +"/bgp:peer-group/bgp:afi-safis/bgp:afi-safi/bgp:l2vpn-vpls" {
    if-feature "vpn-prefix-orf";
    description
      "VPN Prefix ORF augmentation for the L2VPN VPLS address family
       of a BGP peer group.";
    uses orf:orf-capability;
    uses vpn-prefix-orf-quotas;
  }  
  
  augment
   "/rt:routing/rt:control-plane-protocols"
  +"/rt:control-plane-protocol/bgp:bgp/bgp:peer-groups"
  +"/bgp:peer-group/bgp:afi-safis/bgp:afi-safi/bgp:l2vpn-evpn" {
    if-feature "vpn-prefix-orf";        
    description
      "VPN Prefix ORF augmentation for the L2VPN EVPN address family
       of a BGP peer group.";
    uses orf:orf-capability;
    uses vpn-prefix-orf-quotas;
  }  
}
