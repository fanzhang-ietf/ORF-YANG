module ietf-bgp-orf {
  yang-version 1.1;
  namespace "urn:ietf:params:xml:ns:yang:ietf-bgp-orf";
  prefix orf;

  import ietf-routing {
    prefix rt;
    reference
      "RFC 8349: A YANG Data Model for Routing Management
                 (NMDA Version)";
  }
  import ietf-inet-types {
    prefix inet;
    reference
      "RFC 9911: Common YANG Data Types";
  }
  import ietf-bgp {
    prefix bgp;
    reference
      "RFC XXXX: YANG Model for Border Gateway Protocol (BGP-4)";
  }

  organization
    "IETF Inter-Domain Routing (IDR) Working Group";
  contact
    "WG Web:   https://datatracker.ietf.org/wg/idr
     WG List:  IDR <mailto:idr@ietf.org>

     Editor:   Fan Zhang
               <mailto:zhangf52@chinatelecom.cn>
     Editor:   Aijun Wang
               <mailto:wangaj3@chinatelecom.cn>
     Editor:   Changwang Lin
               <mailto:linchangwang.04414@h3c.com>";
  description
    "This YANG module defines a generic configurtion and management
     for the BGP Outbound Route Filtering (ORF). Type-specific ORF
     modules may augment this module.

     The key words 'MUST', 'MUST NOT', 'REQUIRED', 'SHALL', 'SHALL
     NOT', 'SHOULD', 'SHOULD NOT', 'RECOMMENDED', 'NOT RECOMMENDED',
     'MAY', and 'OPTIONAL' in this document are to be interpreted as
     described in BCP 14 (RFC 2119) (RFC 8174) when, and only when,
     they appear in all capitals, as shown here.

     Copyright (c) 2026 IETF Trust and the persons identified as
     authors of the code. All rights reserved.

     Redistribution and use in source and binary forms, with or
     without modification, is permitted pursuant to, and subject to
     the license terms contained in, the Revised BSD License set
     forth in Section 4.c of the IETF Trust's Legal Provisions
     Relating to IETF Documents
     (https://trustee.ietf.org/license-info).

     All revisions of IETF and IANA published modules can be found
     at the YANG Parameters registry group
     (https://www.iana.org/assignments/yang-parameters).

     This version of this YANG module is part of RFC XXXX; see
     the RFC itself for full legal notices.";

  revision 2026-06-18 {
    description
      "Initial revision.";
    reference
      "RFC 5291: Outbound Route Filtering Capability for BGP-4
       RFC 5292: Address-Prefix-Based Outbound Route Filter for
                 BGP-4";
  }

  /*
   * Features
   */

  feature address-prefix-orf {
    description
      "Support for Address Prefix ORF for BGP-4.";
    reference
      "RFC 5292: Address-Prefix-Based Outbound Route Filter for
                 BGP-4";
  }

  /*
   * Identities
   */  

  identity orf-type {
    description
      "Base ORF type.";
    reference
      "RFC 5291: Outbound Route Filtering Capability for BGP-4";
  }

  identity address-prefix-orf {
    base orf-type;
    description
      "Address Prefix ORF.";
    reference
      "RFC 5292: Address-Prefix-Based Outbound Route Filter for
                 BGP-4";
  }

  identity vpn-prefix-orf {
    base orf-type;
    description
      "VPN Prefix ORF.";
    reference
      "RFC XXXX: VPN Prefix Outbound Route Filter (VPN Prefix ORF)
                 for BGP-4";
  }

  /*
   * Typedefs
   */  

  typedef orf-send-receive {
    type enumeration {
      enum receive {
        value 1;
        description
          "The local speaker is willing to receive ORF entries from
           its peer.";
      }
      enum send {
        value 2;
        description
          "The local speaker would like to send ORF entries to its
           peer.";
      }
      enum both {
        value 3;
        description
          "The local speaker supports both sending and receiving ORF
           entries.";
      }
    }
    description
      "ORF Send/Receive field.";
    reference
      "RFC 5291: Outbound Route Filtering Capability for BGP-4,
                 Section 5";
  }

  /*
   * Groupings
   */

  grouping orf-capability {
    description
      "Grouping for ORF Capabilities for a bgp speaker.";
    list capability {
      key "orf-type";
      description
        "List of ORF capabilities for each ORF types.";
      leaf orf-type {
        type identityref {
          base orf-type;
        }
        description
          "The ORF type supoorted by the BGP speaker.";
      }
      leaf send-receive {
        type orf-send-receive;
        default "both";
        description
          "Indicating whether the sender supports receiving ORF
           entries, or sending ORF entries, or both.";
      }
    }
    reference
      "RFC 5291: Outbound Route Filtering Capability for BGP-4,
                 Section 5";
  }

  grouping address-prefix-orf-entries {
    description
      "Grouping for Address Prefix ORF entries for BGP";
    list address-prefix-orf-entry {
      key "sequence";
      description
        "List of Address Prefix ORF entries of an address family.";
      leaf sequence {
        type uint32;
        description
          "Sequence number of the Address Prefix ORF entries.";
      }
      leaf match {
        type enumeration {
          enum permit {
            description
              "Permit the peer to pass updates for the set of routes
               that match the ORF entry.";
          }
          enum deny {
            description
              "Deny the peer to pass the updates for the set of  
               routes that match the ORF entry.";
          }
        }
        description
          "Specifiying whether this entry is PERMIT or DENY.";
      }
      leaf prefix {
        type inet:ip-prefix;
        description
          "IP prefix to be matched by the Address Prefix ORF entry.";
      }
      leaf minlen {
        type uint8;
        description
          "Minimum prefix length (in bits) for matching.
           A value of 0 indicates that the field is unspecified.";
      }
      leaf maxlen {
        type uint8;
        description
          "Maximum prefix length (in bits) for matching.
           A value of 0 indicates that the field is unspecified.";
      }
      reference
        "RFC 5292: Address-Prefix-Based Outbound Route Filter for
                   BGP-4, Section 2";
    }
  }

  /*
   * Data nodes
   */

  augment
    "/rt:routing/rt:control-plane-protocols"
  + "/rt:control-plane-protocol/bgp:bgp/bgp:neighbors/bgp:neighbor"
  + "/bgp:afi-safis/bgp:afi-safi/bgp:ipv4-unicast" {
    if-feature "address-prefix-orf";
    description
      "Address Prefix ORF augmentation for the IPv4 unicast address
       family of a BGP neighbor.";
    uses orf-capability;
    container address-prefix-orf-entries-sent {
      description
        "Address Prefix ORF entries sent";
      uses address-prefix-orf-entries {
        refine "address-prefix-orf-entry/minlen" {
          must '. <= 32';
        }
        refine "address-prefix-orf-entry/maxlen" {
          must '. <= 32';
        }
      }
    }
    container address-prefix-orf-entries-received {
      config false;
      description
        "Address Prefix ORF entries received";
      uses address-prefix-orf-entries {
        refine "address-prefix-orf-entry/minlen" {
          must '. <= 32';
        }
        refine "address-prefix-orf-entry/maxlen" {
          must '. <= 32';
        }
      }
    }
  }

  augment
    "/rt:routing/rt:control-plane-protocols"
  + "/rt:control-plane-protocol/bgp:bgp/bgp:neighbors/bgp:neighbor"
  + "/bgp:afi-safis/bgp:afi-safi/bgp:ipv6-unicast" {
    if-feature "address-prefix-orf";
    description
      "Address Prefix ORF augmentation for the IPv6 unicast address
       family of a BGP neighbor.";
    uses orf-capability;
    container address-prefix-orf-entries-sent {
      description
        "Address Prefix ORF entries sent";
      uses address-prefix-orf-entries {
        refine "address-prefix-orf-entry/minlen" {
          must '. <= 128';
        }
        refine "address-prefix-orf-entry/maxlen" {
          must '. <= 128';
        }
      }
    }
    container address-prefix-orf-entries-received {
      config false;
      description
        "Address Prefix ORF entries received";
      uses address-prefix-orf-entries {
        refine "address-prefix-orf-entry/minlen" {
          must '. <= 128';
        }
        refine "address-prefix-orf-entry/maxlen" {
          must '. <= 128';
        }
      }
    }
  }

  augment
    "/rt:routing/rt:control-plane-protocols"
  + "/rt:control-plane-protocol/bgp:bgp/bgp:peer-groups"
  + "/bgp:peer-group/bgp:afi-safis/bgp:afi-safi/bgp:ipv4-unicast" {
    if-feature "address-prefix-orf";
    description
      "Address Prefix ORF augmentation for the IPv4 unicast address
       family of a BGP peer group.";
    uses orf-capability;
    uses address-prefix-orf-entries {
      refine "address-prefix-orf-entry/minlen" {
        must '. <= 32';
      }
      refine "address-prefix-orf-entry/maxlen" {
        must '. <= 32';
      }
    }
    container address-prefix-orf-entries-sent {
      description
        "Address Prefix ORF entries sent";
      uses address-prefix-orf-entries {
        refine "address-prefix-orf-entry/minlen" {
          must '. <= 32';
        }
        refine "address-prefix-orf-entry/maxlen" {
          must '. <= 32';
        }
      }
    }
  }

  augment
    "/rt:routing/rt:control-plane-protocols"
  + "/rt:control-plane-protocol/bgp:bgp/bgp:peer-groups"
  + "/bgp:peer-group/bgp:afi-safis/bgp:afi-safi/bgp:ipv6-unicast" {
    if-feature "address-prefix-orf";
    description
      "Address Prefix ORF augmentation for the IPv6 unicast address
       family of a BGP peer group.";
    uses orf-capability;
    container address-prefix-orf-entries-sent {
      description
        "Address Prefix ORF entries sent";
      uses address-prefix-orf-entries {
        refine "address-prefix-orf-entry/minlen" {
          must '. <= 128';
        }
        refine "address-prefix-orf-entry/maxlen" {
          must '. <= 128';
        }
      }
    }
  }
}
